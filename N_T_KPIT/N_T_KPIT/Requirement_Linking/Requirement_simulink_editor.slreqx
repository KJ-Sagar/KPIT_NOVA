# Requirement_simulink_editor

## R1_input: input_check (Functional)
which signal uis given to the input

### error_check (Functional)

### saturation: saturation limit check (Functional)
the saturation block is the under the limit?

## R2_PID: PID_Check (Functional)
PID is meeting the requirement?

## R3_Plant_Out: motor_speed (Functional)
is motor is reaching the repuired speed
